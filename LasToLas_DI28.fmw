FME workspace LasToLas_DI28.fmw

Parameters:
- COMPRESSION_LAS =
- DestDataset_LAS =
- MAX_NUM_POINTS =
- VERSION_LAS =

Writers:
- LAS_1: LAS to $(DestDataset_LAS)

Creator
    GEOMTYPE = Geometry Object
    NUM = 1
    CREATED -> FeatureReader_3 [INITIATOR]
Note: FeatureReader_3 [FeatureReader] / Reading: / Reader: / Dataset: https://s3.us-west-2.amazonaws.com/usgs-lidar-public/ARRA-TX_CalhounCo_2010/ / Coordinate System: <not set> / Constraints: / Feature Types to Read: EPT / Feature Type Separator: SPACE / WHERE Clause: <not set> / Spatial Filter: <No Spatial Filter> / Max Features to Read: <not set> / Schema/Data Features: / Features To Read: Schema and Data Features / Output: / Output Ports: / [x] One per Feature Type Regenerate: [ ] / Attribute and Geometry Handling: / Accumulation Mode: Only Use Result / Geometry: Use Result / <Generic> Port: / Attributes to Expose: <not set>
FeatureReader_3
    ATTRIBUTES = EPT,
    ATTR_ACCUM_MODE = Only Use Result
    COMBINE_GEOM = Use Result
    DATASET = https://s3.us-west-2.amazonaws.com/usgs-lidar-public/ARRA-TX_CalhounCo_2010/
    EPT_READER_META_ATTRIBUTES = fme_dataset fme_basename
    EPT_USE_SEARCH_ENVELOPE = NO
    FEATURETYPES = EPT
    FORMAT = EPT
    INTERACT = NONE
    OUTPUT_FEATURES_DISPLAY = Schema and Data Features
    EPT -> PointCloudThinner
PointCloudThinner
    MAX_NUM_POINTS = $(MAX_NUM_POINTS)
    THINNED -> PointCloudSplitter
Note: PointCloudSplitter [PointCloudSplitter] / General: / Split By: classification / Split Type: Unique / Output Attribute: _split_value / Unique Values to Keep (leave empty to keep all): 2
Note: Split by classification not by return
PointCloudSplitter
    OUTPUT_ATTR = _split_value
    SPLIT_BY_DISPLAY = classification
    SPLIT_TYPE = Unique
    VALUE_LIST = 2
    SPLIT -> Class_2 (writer LAS_1)
Class_2 (writer LAS_1)

Bookmark: Notes
Note: [USGS Entwine viewer](https://usgs.entwine.io/)
Note: 709000000
