FME workspace EptLasToRaster28Incomplete.fmw

Note: [USGS Entwine viewer](https://usgs.entwine.io/)
Creator
    GEOMTYPE = Geometry Object
    NUM = 1
    CREATED -> FeatureReader_3 [INITIATOR]
Note: FeatureReader_3 [FeatureReader] / Reading: / Reader: / Dataset: https://s3.us-west-2.amazonaws.com/usgs-lidar-public/ARRA-TX_CalhounCo_2010/ / Coordinate System: <not set> / Constraints: / Feature Types to Read: EPT / Feature Type Separator: SPACE / WHERE Clause: <not set> / Spatial Filter: <No Spatial Filter> / Max Features to Read: <not set> / Schema/Data Features: / Features To Read: Schema and Data Features / Output: / Output Ports: / [x] One per Feature Type Regenerate: [ ] / Attribute and Geometry Handling: / Accumulation Mode: Only Use Result / Geometry: Use Result / <Generic> Port: / Attributes to Expose: <not set>
Note: Read Project Entwine EPT.JSON
FeatureReader_3
    ATTRIBUTES = EPT,
    ATTR_ACCUM_MODE = Only Use Result
    COMBINE_GEOM = Use Result
    DATASET = https://s3.us-west-2.amazonaws.com/usgs-lidar-public/ARRA-TX_CalhounCo_2010/
    EPT_READER_META_ATTRIBUTES = fme_dataset fme_basename
    EPT_USE_SEARCH_ENVELOPE = NO
    FEATURETYPES = EPT
    FORMAT = EPT
    INTERACT = NONE
    OUTPUT_FEATURES_DISPLAY = Schema and Data Features
    EPT -> PointCloudSplitter
PointCloudSplitter
    OUTPUT_ATTR = _split_value
    SPLIT_BY_DISPLAY = return
    SPLIT_TYPE = Unique
    VALUE_LIST = 2
    SPLIT -> SurfaceModeller [POINTS/LINES]
SurfaceModeller
    ADDZ_TYPE = Replace Z
    CONTOUR_DIMENSION = 3
    CONTOUR_INTERVAL = 100.0
    DRAPE_TYPE = VERTEX
    IGNORE_INPUT_ON_INTERVAL = Perturb Input Points On Contour Interval
    INTERPOLATION_TYPE = AUTO
    NODATA_VALUE = -32767.0
    TOLERANCE = 100
    X_SPACING = 100.0
    Y_SPACING = 100.0
    DEMRaster -> PointCloudSplitter_Split
PointCloudSplitter_Split: Inspector
